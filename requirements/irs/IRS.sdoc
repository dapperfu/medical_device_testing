[DOCUMENT]
TITLE: Interface Requirements Specification
UID: DOC-IRS
VERSION: 0.1.0
DATE: 2026-10-20

[[SECTION]]
TITLE: Patient monitor interface

[REQUIREMENT]
UID: IRS001
TITLE: attach
STATEMENT: attach shall accept a Human and shall select the default limit profile for that patient's age.
RELATIONS:
- TYPE: Parent
  VALUE: SSS005

[REQUIREMENT]
UID: IRS002
TITLE: start and stop
STATEMENT: start shall begin monitoring when a patient is attached and shall reject a start when no patient is attached. stop shall end monitoring.
RELATIONS:
- TYPE: Parent
  VALUE: SSS004

[REQUIREMENT]
UID: IRS003
TITLE: set_limits
STATEMENT: set_limits shall accept an in-range AlarmLimits and shall raise LimitRejected without changing the limits already in effect when the command is out of range.
RELATIONS:
- TYPE: Parent
  VALUE: SSS007

[REQUIREMENT]
UID: IRS004
TITLE: vitals and alarms
STATEMENT: vitals shall return a reading whose valid flag is true only while monitoring is running with a valid sensor. alarms shall return the active alarm set and shall return an empty set when monitoring is not running.
RELATIONS:
- TYPE: Parent
  VALUE: SSS001
- TYPE: Parent
  VALUE: SSS006

[REQUIREMENT]
UID: IRS005
TITLE: SOAP GetPatient
STATEMENT: GetPatient shall accept a patientId and shall return that patient's identity, age, vitals, and sensor validity, or a SOAP fault when the patient is unknown or the request is malformed.
RELATIONS:
- TYPE: Parent
  VALUE: SSS010
- TYPE: Parent
  VALUE: SSS011

[REQUIREMENT]
UID: IRS006
TITLE: ReadyAPI patient resource
STATEMENT: GET /patients/{patient_id} shall return that patient's identity, age, vitals, and sensor validity as JSON, or status 404 when the patient is unknown.
RELATIONS:
- TYPE: Parent
  VALUE: SSS012
- TYPE: Parent
  VALUE: SSS013

[[/SECTION]]
